(arxload "PnP3dACPAdapter.arx")
(testacpscript1 "CPFBR" "L=0.4400,D=3.5000")
(command "_.move" (entlast) "" "0,0,0" "100,0,0")
(testacpscript1 "CPFBR" "L=0.5000,D=3.8800")
(command "_.move" (entlast) "" "0,0,0" "200,0,0")
(testacpscript1 "CPFBR" "L=0.5600,D=4.2500")
(command "_.move" (entlast) "" "0,0,0" "300,0,0")
(testacpscript1 "CPFBR" "L=0.6800,D=5.0000")
(command "_.move" (entlast) "" "0,0,0" "400,0,0")
(testacpscript1 "CPFBR" "L=0.7500,D=6.0000")
(command "_.move" (entlast) "" "0,0,0" "500,0,0")
(testacpscript1 "CPFBR" "L=0.9400,D=7.5000")
(command "_.move" (entlast) "" "0,0,0" "600,0,0")
(testacpscript1 "CPFBR" "L=0.9400,D=9.0000")
(command "_.move" (entlast) "" "0,0,0" "700,0,0")
(testacpscript1 "CPFBR" "L=1.0000,D=11.0000")
(command "_.move" (entlast) "" "0,0,0" "800,0,0")
(testacpscript1 "CPFBR" "L=1.1200,D=13.5000")
(command "_.move" (entlast) "" "0,0,0" "900,0,0")
(testacpscript1 "CPFBR" "L=1.1800,D=16.0000")
(command "_.move" (entlast) "" "0,0,0" "1000,0,0")
(testacpscript1 "CPFBR" "L=1.2500,D=19.0000")
(command "_.move" (entlast) "" "0,0,0" "1100,0,0")
(testacpscript1 "CPFBR" "L=1.3700,D=21.0000")
(command "_.move" (entlast) "" "0,0,0" "1200,0,0")
(testacpscript1 "CPFBR" "L=1.4400,D=23.5000")
(command "_.move" (entlast) "" "0,0,0" "1300,0,0")
(testacpscript1 "CPFBR" "L=1.5600,D=25.0000")
(command "_.move" (entlast) "" "0,0,0" "1400,0,0")
(testacpscript1 "CPFBR" "L=1.6800,D=27.5000")
(command "_.move" (entlast) "" "0,0,0" "1500,0,0")
(testacpscript1 "CPFBR" "L=1.8700,D=32.0000")
(command "_.move" (entlast) "" "0,0,0" "0,0,0")
(testacpscript1 "CPFBR" "L=0.4400,D=3.5000")
(command "_.move" (entlast) "" "0,0,0" "100,0,0")
(testacpscript1 "CPFBR" "L=0.5000,D=3.8800")
(command "_.move" (entlast) "" "0,0,0" "200,0,0")
(testacpscript1 "CPFBR" "L=0.5600,D=4.2500")
(command "_.move" (entlast) "" "0,0,0" "300,0,0")
(testacpscript1 "CPFBR" "L=0.6800,D=5.0000")
(command "_.move" (entlast) "" "0,0,0" "400,0,0")
(testacpscript1 "CPFBR" "L=0.7500,D=6.0000")
(command "_.move" (entlast) "" "0,0,0" "500,0,0")
(testacpscript1 "CPFBR" "L=0.9400,D=7.5000")
(command "_.move" (entlast) "" "0,0,0" "600,0,0")
(testacpscript1 "CPFBR" "L=0.9400,D=9.0000")
(command "_.move" (entlast) "" "0,0,0" "700,0,0")
(testacpscript1 "CPFBR" "L=1.0000,D=11.0000")
(command "_.move" (entlast) "" "0,0,0" "800,0,0")
(testacpscript1 "CPFBR" "L=1.1200,D=13.5000")
(command "_.move" (entlast) "" "0,0,0" "900,0,0")
(testacpscript1 "CPFBR" "L=1.1800,D=16.0000")
(command "_.move" (entlast) "" "0,0,0" "1000,0,0")
(testacpscript1 "CPFBR" "L=1.2500,D=19.0000")
(command "_.move" (entlast) "" "0,0,0" "1100,0,0")
(testacpscript1 "CPFBR" "L=1.3700,D=21.0000")
(command "_.move" (entlast) "" "0,0,0" "1200,0,0")
(testacpscript1 "CPFBR" "L=1.4400,D=23.5000")
(command "_.move" (entlast) "" "0,0,0" "1300,0,0")
(testacpscript1 "CPFBR" "L=1.5600,D=25.0000")
(command "_.move" (entlast) "" "0,0,0" "1400,0,0")
(testacpscript1 "CPFBR" "L=1.6800,D=27.5000")
(command "_.move" (entlast) "" "0,0,0" "1500,0,0")
(testacpscript1 "CPFBR" "L=1.8700,D=32.0000")
(command "_.move" (entlast) "" "0,0,0" "0,0,0")
(testacpscript1 "CPFBR" "L=0.4400,D=3.5000")
(command "_.move" (entlast) "" "0,0,0" "100,0,0")
(testacpscript1 "CPFBR" "L=0.5000,D=3.8800")
(command "_.move" (entlast) "" "0,0,0" "200,0,0")
(testacpscript1 "CPFBR" "L=0.5600,D=4.2500")
(command "_.move" (entlast) "" "0,0,0" "300,0,0")
(testacpscript1 "CPFBR" "L=0.6800,D=5.0000")
(command "_.move" (entlast) "" "0,0,0" "400,0,0")
(testacpscript1 "CPFBR" "L=0.7500,D=6.0000")
(command "_.move" (entlast) "" "0,0,0" "500,0,0")
(testacpscript1 "CPFBR" "L=0.9400,D=7.5000")
(command "_.move" (entlast) "" "0,0,0" "600,0,0")
(testacpscript1 "CPFBR" "L=0.9400,D=9.0000")
(command "_.move" (entlast) "" "0,0,0" "700,0,0")
(testacpscript1 "CPFBR" "L=1.0000,D=11.0000")
(command "_.move" (entlast) "" "0,0,0" "800,0,0")
(testacpscript1 "CPFBR" "L=1.1200,D=13.5000")
(command "_.move" (entlast) "" "0,0,0" "900,0,0")
(testacpscript1 "CPFBR" "L=1.1800,D=16.0000")
(command "_.move" (entlast) "" "0,0,0" "1000,0,0")
(testacpscript1 "CPFBR" "L=1.2500,D=19.0000")
(command "_.move" (entlast) "" "0,0,0" "1100,0,0")
(testacpscript1 "CPFBR" "L=1.3700,D=21.0000")
(command "_.move" (entlast) "" "0,0,0" "1200,0,0")
(testacpscript1 "CPFBR" "L=1.4400,D=23.5000")
(command "_.move" (entlast) "" "0,0,0" "1300,0,0")
(testacpscript1 "CPFBR" "L=1.5600,D=25.0000")
(command "_.move" (entlast) "" "0,0,0" "1400,0,0")
(testacpscript1 "CPFBR" "L=1.6800,D=27.5000")
(command "_.move" (entlast) "" "0,0,0" "1500,0,0")
(testacpscript1 "CPFBR" "L=1.8700,D=32.0000")
(command "_.move" (entlast) "" "0,0,0" "0,0,0")
(testacpscript1 "CPFBR" "L=0.4400,D=3.5000")
(command "_.move" (entlast) "" "0,0,0" "100,0,0")
(testacpscript1 "CPFBR" "L=0.5000,D=3.8800")
(command "_.move" (entlast) "" "0,0,0" "200,0,0")
(testacpscript1 "CPFBR" "L=0.5600,D=4.2500")
(command "_.move" (entlast) "" "0,0,0" "300,0,0")
(testacpscript1 "CPFBR" "L=0.6800,D=5.0000")
(command "_.move" (entlast) "" "0,0,0" "400,0,0")
(testacpscript1 "CPFBR" "L=0.7500,D=6.0000")
(command "_.move" (entlast) "" "0,0,0" "500,0,0")
(testacpscript1 "CPFBR" "L=0.9400,D=7.5000")
(command "_.move" (entlast) "" "0,0,0" "600,0,0")
(testacpscript1 "CPFBR" "L=0.9400,D=9.0000")
(command "_.move" (entlast) "" "0,0,0" "700,0,0")
(testacpscript1 "CPFBR" "L=1.0000,D=11.0000")
(command "_.move" (entlast) "" "0,0,0" "800,0,0")
(testacpscript1 "CPFBR" "L=1.1200,D=13.5000")
(command "_.move" (entlast) "" "0,0,0" "900,0,0")
(testacpscript1 "CPFBR" "L=1.1800,D=16.0000")
(command "_.move" (entlast) "" "0,0,0" "1000,0,0")
(testacpscript1 "CPFBR" "L=1.2500,D=19.0000")
(command "_.move" (entlast) "" "0,0,0" "1100,0,0")
(testacpscript1 "CPFBR" "L=1.3700,D=21.0000")
(command "_.move" (entlast) "" "0,0,0" "1200,0,0")
(testacpscript1 "CPFBR" "L=1.4400,D=23.5000")
(command "_.move" (entlast) "" "0,0,0" "1300,0,0")
(testacpscript1 "CPFBR" "L=1.5600,D=25.0000")
(command "_.move" (entlast) "" "0,0,0" "1400,0,0")
(testacpscript1 "CPFBR" "L=1.6800,D=27.5000")
(command "_.move" (entlast) "" "0,0,0" "1500,0,0")
(testacpscript1 "CPFBR" "L=1.8700,D=32.0000")
(command "_.move" (entlast) "" "0,0,0" "0,0,0")
(testacpscript1 "CPFBR" "L=0.4400,D=3.5000")
(command "_.move" (entlast) "" "0,0,0" "100,0,0")
(testacpscript1 "CPFBR" "L=0.5000,D=3.8800")
(command "_.move" (entlast) "" "0,0,0" "200,0,0")
(testacpscript1 "CPFBR" "L=0.5600,D=4.2500")
(command "_.move" (entlast) "" "0,0,0" "300,0,0")
(testacpscript1 "CPFBR" "L=0.6800,D=5.0000")
(command "_.move" (entlast) "" "0,0,0" "400,0,0")
(testacpscript1 "CPFBR" "L=0.7500,D=6.0000")
(command "_.move" (entlast) "" "0,0,0" "500,0,0")
(testacpscript1 "CPFBR" "L=0.9400,D=7.5000")
(command "_.move" (entlast) "" "0,0,0" "600,0,0")
(testacpscript1 "CPFBR" "L=0.9400,D=9.0000")
(command "_.move" (entlast) "" "0,0,0" "700,0,0")
(testacpscript1 "CPFBR" "L=1.0000,D=11.0000")
(command "_.move" (entlast) "" "0,0,0" "800,0,0")
(testacpscript1 "CPFBR" "L=1.1200,D=13.5000")
(command "_.move" (entlast) "" "0,0,0" "900,0,0")
(testacpscript1 "CPFBR" "L=1.1800,D=16.0000")
(command "_.move" (entlast) "" "0,0,0" "1000,0,0")
(testacpscript1 "CPFBR" "L=1.2500,D=19.0000")
(command "_.move" (entlast) "" "0,0,0" "1100,0,0")
(testacpscript1 "CPFBR" "L=1.3700,D=21.0000")
(command "_.move" (entlast) "" "0,0,0" "1200,0,0")
(testacpscript1 "CPFBR" "L=1.4400,D=23.5000")
(command "_.move" (entlast) "" "0,0,0" "1300,0,0")
(testacpscript1 "CPFBR" "L=1.5600,D=25.0000")
(command "_.move" (entlast) "" "0,0,0" "1400,0,0")
(testacpscript1 "CPFBR" "L=1.6800,D=27.5000")
(command "_.move" (entlast) "" "0,0,0" "1500,0,0")
(testacpscript1 "CPFBR" "L=1.8700,D=32.0000")
(command "_.move" (entlast) "" "0,0,0" "0,0,0")
(testacpscript1 "CPFBR" "L=0.4400,D=3.5000")
(command "_.move" (entlast) "" "0,0,0" "100,0,0")
(testacpscript1 "CPFBR" "L=0.5000,D=3.8800")
(command "_.move" (entlast) "" "0,0,0" "200,0,0")
(testacpscript1 "CPFBR" "L=0.5600,D=4.2500")
(command "_.move" (entlast) "" "0,0,0" "300,0,0")
(testacpscript1 "CPFBR" "L=0.6800,D=5.0000")
(command "_.move" (entlast) "" "0,0,0" "400,0,0")
(testacpscript1 "CPFBR" "L=0.7500,D=6.0000")
(command "_.move" (entlast) "" "0,0,0" "500,0,0")
(testacpscript1 "CPFBR" "L=0.9400,D=7.5000")
(command "_.move" (entlast) "" "0,0,0" "600,0,0")
(testacpscript1 "CPFBR" "L=0.9400,D=9.0000")
(command "_.move" (entlast) "" "0,0,0" "700,0,0")
(testacpscript1 "CPFBR" "L=1.0000,D=11.0000")
(command "_.move" (entlast) "" "0,0,0" "800,0,0")
(testacpscript1 "CPFBR" "L=1.1200,D=13.5000")
(command "_.move" (entlast) "" "0,0,0" "900,0,0")
(testacpscript1 "CPFBR" "L=1.1800,D=16.0000")
(command "_.move" (entlast) "" "0,0,0" "1000,0,0")
(testacpscript1 "CPFBR" "L=1.2500,D=19.0000")
(command "_.move" (entlast) "" "0,0,0" "1100,0,0")
(testacpscript1 "CPFBR" "L=1.3700,D=21.0000")
(command "_.move" (entlast) "" "0,0,0" "1200,0,0")
(testacpscript1 "CPFBR" "L=1.4400,D=23.5000")
(command "_.move" (entlast) "" "0,0,0" "1300,0,0")
(testacpscript1 "CPFBR" "L=1.5600,D=25.0000")
(command "_.move" (entlast) "" "0,0,0" "1400,0,0")
(testacpscript1 "CPFBR" "L=1.6800,D=27.5000")
(command "_.move" (entlast) "" "0,0,0" "1500,0,0")
(testacpscript1 "CPFBR" "L=1.8700,D=32.0000")
(command "_.move" (entlast) "" "0,0,0" "0,0,0")
(testacpscript1 "CPFBR" "L=0.4400,D=3.5000")
(command "_.move" (entlast) "" "0,0,0" "100,0,0")
(testacpscript1 "CPFBR" "L=0.5000,D=3.8800")
(command "_.move" (entlast) "" "0,0,0" "200,0,0")
(testacpscript1 "CPFBR" "L=0.5600,D=4.2500")
(command "_.move" (entlast) "" "0,0,0" "300,0,0")
(testacpscript1 "CPFBR" "L=0.6800,D=5.0000")
(command "_.move" (entlast) "" "0,0,0" "400,0,0")
(testacpscript1 "CPFBR" "L=0.7500,D=6.0000")
(command "_.move" (entlast) "" "0,0,0" "500,0,0")
(testacpscript1 "CPFBR" "L=0.9400,D=7.5000")
(command "_.move" (entlast) "" "0,0,0" "600,0,0")
(testacpscript1 "CPFBR" "L=0.9400,D=9.0000")
(command "_.move" (entlast) "" "0,0,0" "700,0,0")
(testacpscript1 "CPFBR" "L=1.0000,D=11.0000")
(command "_.move" (entlast) "" "0,0,0" "800,0,0")
(testacpscript1 "CPFBR" "L=1.1200,D=13.5000")
(command "_.move" (entlast) "" "0,0,0" "900,0,0")
(testacpscript1 "CPFBR" "L=1.1800,D=16.0000")
(command "_.move" (entlast) "" "0,0,0" "1000,0,0")
(testacpscript1 "CPFBR" "L=1.2500,D=19.0000")
(command "_.move" (entlast) "" "0,0,0" "1100,0,0")
(testacpscript1 "CPFBR" "L=1.3700,D=21.0000")
(command "_.move" (entlast) "" "0,0,0" "1200,0,0")
(testacpscript1 "CPFBR" "L=1.4400,D=23.5000")
(command "_.move" (entlast) "" "0,0,0" "1300,0,0")
(testacpscript1 "CPFBR" "L=1.5600,D=25.0000")
(command "_.move" (entlast) "" "0,0,0" "1400,0,0")
(testacpscript1 "CPFBR" "L=1.6800,D=27.5000")
(command "_.move" (entlast) "" "0,0,0" "1500,0,0")
(testacpscript1 "CPFBR" "L=1.8700,D=32.0000")
