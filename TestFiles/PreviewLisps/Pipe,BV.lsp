(arxload "PnP3dACPAdapter.arx")
(testacpscript1 "CPP" "")
(command "_.move" (entlast) "" "0,0,0" "100,0,0")
(testacpscript1 "CPP" "")
(command "_.move" (entlast) "" "0,0,0" "200,0,0")
(testacpscript1 "CPP" "")
(command "_.move" (entlast) "" "0,0,0" "300,0,0")
(testacpscript1 "CPP" "")
(command "_.move" (entlast) "" "0,0,0" "400,0,0")
(testacpscript1 "CPP" "")
(command "_.move" (entlast) "" "0,0,0" "500,0,0")
(testacpscript1 "CPP" "")
(command "_.move" (entlast) "" "0,0,0" "600,0,0")
(testacpscript1 "CPP" "")
(command "_.move" (entlast) "" "0,0,0" "700,0,0")
(testacpscript1 "CPP" "")
(command "_.move" (entlast) "" "0,0,0" "800,0,0")
(testacpscript1 "CPP" "")
(command "_.move" (entlast) "" "0,0,0" "900,0,0")
(testacpscript1 "CPP" "")
(command "_.move" (entlast) "" "0,0,0" "1000,0,0")
(testacpscript1 "CPP" "")
(command "_.move" (entlast) "" "0,0,0" "1100,0,0")
(testacpscript1 "CPP" "")
